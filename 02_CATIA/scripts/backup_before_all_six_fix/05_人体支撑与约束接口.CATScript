' =====================================================================
' 05_人体支撑与约束接口.CATScript  (CATIA V5, VBScript)
' 在运行完 01~04 后运行：
'   1) 躯干托板 Cradle —— 俯卧承托板 1000x400x10（贴合体型，简化为平板）
'   2) 载荷挂带 Harness —— 4 根芳纶织带（50x5 竖条）+ 挂点耳环 + 挂点吊杆
'   3) 约束接口 Constraints —— 供 03_FEA 施加边界条件的命名点：
'         HangPoint(挂点) / LegTouchL,R(双腿触地) / PropThrust(螺旋桨推力点)
' =====================================================================
Sub CATMain()
    Dim part
    Set part = CATIA.ActiveDocument.Part

    EnsureParam part, "CradleLen", "LENGTH", 1000.0
    EnsureParam part, "CradleWid", "LENGTH", 400.0
    EnsureParam part, "CradleThk", "LENGTH", 10.0

    Dim gs
    Set gs = AddGS(part, "HumanSupport_Ref")

    Dim hangX, hangZ, cradleZ
    hangX = 500.0
    hangZ = -350.0
    cradleZ = -460.0

    ' =================================================================
    ' 1) 躯干托板 Cradle（平板 1000x400x10，中心 (700,0,-460)）
    ' =================================================================
    Dim bodyCradle, cL, cW, cT
    Set bodyCradle = NewBody(part, "Cradle")
    cL = ParamValue(part, "CradleLen")
    cW = ParamValue(part, "CradleWid")
    cT = ParamValue(part, "CradleThk")
    AddBox part, bodyCradle, gs, "Cradle", "Z", cradleZ - cT / 2.0, _
           700.0 - cL / 2.0, -cW / 2.0, 700.0 + cL / 2.0, cW / 2.0, cT, False

    ' =================================================================
    ' 2) 载荷挂带 Harness（4 织带 + 挂点吊杆 + 挂点耳环）
    ' =================================================================
    Dim bodyHarn
    Set bodyHarn = NewBody(part, "Harness")

    ' 4 根芳纶织带（竖条 50x5，z=-460..-350）
    AddBox part, bodyHarn, gs, "StrapFL", "Z", cradleZ, 375.0,  97.5, 425.0, 102.5, hangZ - cradleZ, False
    AddBox part, bodyHarn, gs, "StrapFR", "Z", cradleZ, 375.0, -102.5, 425.0, -97.5, hangZ - cradleZ, False
    AddBox part, bodyHarn, gs, "StrapRL", "Z", cradleZ, 675.0,  97.5, 725.0, 102.5, hangZ - cradleZ, False
    AddBox part, bodyHarn, gs, "StrapRR", "Z", cradleZ, 675.0, -102.5, 725.0, -97.5, hangZ - cradleZ, False

    ' 挂点吊杆（龙骨 z=-250 到耳环 z=-350，φ12 竖杆，沿 Z）
    AddCylinder part, bodyHarn, gs, "HangLink", "Z", -250.0, hangX, 0.0, 6.0, 0.0, 100.0, False
    ' 挂点耳环（φ20 沿 X，长 30，位于 (500,0,-350)）
    AddCylinder part, bodyHarn, gs, "HangRing", "X", hangX - 15.0, 0.0, hangZ, 10.0, 0.0, 30.0, False

    ' =================================================================
    ' 3) 约束接口（命名点，供 FEA）
    ' =================================================================
    Dim gsC, hsf, pt
    Set gsC = AddGS(part, "Constraints")
    Set hsf = part.HybridShapeFactory

    Set pt = hsf.AddNewPointCoord(hangX, 0.0, hangZ) : pt.Name = "HangPoint"
    gsC.AppendHybridShape pt
    Set pt = hsf.AddNewPointCoord(1200.0,  150.0, -460.0) : pt.Name = "LegTouchL"
    gsC.AppendHybridShape pt
    Set pt = hsf.AddNewPointCoord(1200.0, -150.0, -460.0) : pt.Name = "LegTouchR"
    gsC.AppendHybridShape pt
    Set pt = hsf.AddNewPointCoord(1440.0, 0.0, 200.0) : pt.Name = "PropThrust"
    gsC.AppendHybridShape pt

    part.Update

    MsgBox "人体支撑与约束接口已生成：" & vbCrLf & _
           "  Cradle —— 躯干托板 1000x400x10" & vbCrLf & _
           "  Harness —— 4 根挂带 + 挂点吊杆 + 挂点耳环" & vbCrLf & _
           "  Constraints —— HangPoint / LegTouchL,R / PropThrust" & vbCrLf & _
           "下一步：运行 06_检查与导出.CATScript"
End Sub

' ---------------------------------------------------------------------
' 通用：矩形盒 / 圆柱（同 04 脚本，自包含）
' ---------------------------------------------------------------------
Sub AddCylinder(part, body, gs, name, key, off, cx, cy, rOut, rIn, len1, reverse)
    Dim planeRef
    Set planeRef = PlaneOffset(part, gs, key, off)
    Dim sk
    Set sk = body.Sketches.Add(planeRef)
    sk.Name = name & "_sk"
    SetAxisKey sk, key, off
    Dim f2d
    Set f2d = sk.OpenEdition()
    f2d.CreateClosedCircle cx, cy, rOut
    If rIn > 0.0 Then f2d.CreateClosedCircle cx, cy, rIn
    sk.CloseEdition
    part.InWorkObject = body
    Dim pad
    Set pad = part.ShapeFactory.AddNewPad(sk, len1)
    pad.Name = name
    If reverse Then pad.FirstLimit.Length = 0.0 : pad.SecondLimit.Length = len1
End Sub

Sub AddBox(part, body, gs, name, key, off, u1, v1, u2, v2, len1, reverse)
    Dim planeRef
    Set planeRef = PlaneOffset(part, gs, key, off)
    Dim sk
    Set sk = body.Sketches.Add(planeRef)
    sk.Name = name & "_sk"
    SetAxisKey sk, key, off
    Dim f2d
    Set f2d = sk.OpenEdition()
    f2d.CreateLine u1, v1, u2, v1
    f2d.CreateLine u2, v1, u2, v2
    f2d.CreateLine u2, v2, u1, v2
    f2d.CreateLine u1, v2, u1, v1
    sk.CloseEdition
    part.InWorkObject = body
    Dim pad
    Set pad = part.ShapeFactory.AddNewPad(sk, len1)
    pad.Name = name
    If reverse Then pad.FirstLimit.Length = 0.0 : pad.SecondLimit.Length = len1
End Sub

Function PlaneOffset(part, gs, key, off)
    Static cnt
    Dim hsf, refBase, po
    cnt = cnt + 1
    Set hsf = part.HybridShapeFactory
    If key = "X" Then
        Set refBase = part.CreateReferenceFromObject(part.OriginElements.PlaneYZ)
    ElseIf key = "Z" Then
        Set refBase = part.CreateReferenceFromObject(part.OriginElements.PlaneXY)
    Else
        Set refBase = part.CreateReferenceFromObject(part.OriginElements.PlaneZX)
    End If
    Set po = hsf.AddNewPlaneOffset(refBase, off, False)
    po.Name = "Plane_" & key & "_" & cnt
    gs.AppendHybridShape po
    Set PlaneOffset = part.CreateReferenceFromObject(po)
End Function

Sub SetAxisKey(sk, key, off)
    If key = "X" Then
        SetAxis sk, off, 0.0, 0.0, 0.0, 1.0, 0.0, 0.0, 0.0, 1.0
    ElseIf key = "Z" Then
        SetAxis sk, 0.0, 0.0, off, 1.0, 0.0, 0.0, 0.0, 1.0, 0.0
    Else
        SetAxis sk, 0.0, off, 0.0, 1.0, 0.0, 0.0, 0.0, 0.0, 1.0
    End If
End Sub

Sub SetAxis(sk, ox, oy, oz, hx, hy, hz, vx, vy, vz)
    Dim a(8)
    a(0) = ox : a(1) = oy : a(2) = oz
    a(3) = hx : a(4) = hy : a(5) = hz
    a(6) = vx : a(7) = vy : a(8) = vz
    sk.SetAbsoluteAxisData a
End Sub

Function ParamValue(part, name)
    Dim p
    For Each p In part.Parameters
        If p.Name = name Then
            ParamValue = p.Value
            Exit Function
        End If
    Next
    ParamValue = 0.0
End Function

Sub EnsureParam(part, name, kind, val)
    Dim p, exists
    exists = False
    For Each p In part.Parameters
        If p.Name = name Then exists = True
    Next
    If Not exists Then
        If kind = "LENGTH" Then
            Set p = part.Parameters.CreateDimension("", "LENGTH", val)
        Else
            Set p = part.Parameters.CreateReal("", val)
        End If
        p.Rename name
    End If
End Sub

Function AddGS(part, name)
    Dim gs
    Set gs = part.HybridBodies.Add()
    gs.Name = name
    Set AddGS = gs
End Function

Function NewBody(part, name)
    Dim b
    Set b = part.Bodies.Add()
    b.Name = name
    part.InWorkObject = b
    Set NewBody = b
End Function

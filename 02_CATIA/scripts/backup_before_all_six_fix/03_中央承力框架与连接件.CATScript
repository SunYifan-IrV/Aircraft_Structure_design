' =====================================================================
' 03_中央承力框架与连接件.CATScript  (CATIA V5, VBScript)
' 在运行完 01、02 后运行（活动零件已有 Skeleton / WingSurface / 翼面结构件）：
'   1) 中央承力盒 CentralBox —— 空心盒梁，展向 y=-800..+800，贯通左右翼根
'   2) 龙骨 Keel —— 纵向铝管 φ40x3，沿 X 0..1800，y=0，z=-250
'   3) 龙骨竖支杆 KeelStrut —— 2 根 φ20x2，连接中央盒底(z~5)与龙骨(z=-250)
'   4) 翼根折叠铰 RootHinge —— 每侧 3 处（主梁上/下缘条 + 后梁），
'      每处：7075-T6 铰耳(带销孔) + 钢销
' =====================================================================
Sub CATMain()
    Dim part
    Set part = CATIA.ActiveDocument.Part

    EnsureParam part, "CentralBoxSpan",  "LENGTH", 1600.0
    EnsureParam part, "CentralBoxWidth", "LENGTH", 160.0
    EnsureParam part, "HingeY",          "LENGTH", 800.0
    EnsureParam part, "KeelLength",      "LENGTH", 1800.0
    EnsureParam part, "KeelDiameter",    "LENGTH", 40.0

    Dim rootChord, tipChord, halfSpan, dihedralDeg
    Dim sparPos, rearPos, sparDepth, rearDepth, sparCam, rearCam, wall
    rootChord   = ParamValue(part, "RootChord")
    tipChord    = ParamValue(part, "TipChord")
    halfSpan    = ParamValue(part, "WingSpan") / 2.0
    dihedralDeg = ParamValue(part, "Dihedral")
    sparPos     = ParamValue(part, "SparChordPos")
    rearPos     = ParamValue(part, "RearSparChordPos")
    sparDepth   = ParamValue(part, "SparDepthRoot")
    rearDepth   = ParamValue(part, "RearSparDepthRoot")
    sparCam     = ParamValue(part, "SparCamber")
    rearCam     = ParamValue(part, "RearSparCamber")
    wall        = ParamValue(part, "WallThickness")

    Dim gs
    Set gs = AddGS(part, "CentralFrame_Ref")

    ' =================================================================
    ' 1) 中央承力盒（空心盒梁，y=-800..800，中心在 30% 弦、翼型中厚线）
    ' =================================================================
    Dim bodyBox, cboxW, cboxD, cboxXc, cboxZc, cboxHalf
    Set bodyBox = NewBody(part, "CentralBox")
    cboxW = ParamValue(part, "CentralBoxWidth")
    cboxD = sparDepth
    cboxXc = sparPos * rootChord
    cboxZc = sparCam * rootChord
    cboxHalf = ParamValue(part, "CentralBoxSpan") / 2.0
    AddHollowBoxSym part, bodyBox, gs, "CentralBox", 0.0, cboxXc, cboxZc, _
                    cboxW, cboxD, wall, cboxHalf

    ' =================================================================
    ' 2) 龙骨（纵向铝管，沿 X；草图在 YZ 面，圆中心 (y=0,z=-250)）
    ' =================================================================
    Dim bodyKeel, keelLen, keelDia
    Set bodyKeel = NewBody(part, "Keel")
    keelLen = ParamValue(part, "KeelLength")
    keelDia = ParamValue(part, "KeelDiameter")
    AddCylinder part, bodyKeel, gs, "Keel", "X", 0.0, 0.0, -250.0, _
                keelDia / 2.0, keelDia / 2.0 - wall, keelLen, False

    ' =================================================================
    ' 3) 龙骨竖支杆（中央盒底 z~5 到龙骨 z=-250，2 根 φ20x2，x=560/670）
    ' =================================================================
    Dim bodyStrut, strutLen
    Set bodyStrut = NewBody(part, "KeelStrut")
    strutLen = (cboxZc - cboxD / 2.0) - (-250.0)      ' ≈ 255
    AddCylinder part, bodyStrut, gs, "StrutFwd", "Z", -250.0, 560.0, 0.0, 10.0, 8.0, strutLen, False
    AddCylinder part, bodyStrut, gs, "StrutAft", "Z", -250.0, 670.0, 0.0, 10.0, 8.0, strutLen, False

    ' =================================================================
    ' 4) 翼根折叠铰（每侧 3 处）
    ' =================================================================
    Dim bodyHinge
    Set bodyHinge = NewBody(part, "RootHinge")

    Dim hy, c800, xM, zMup, zMlo, xR, zR, zd
    hy = ParamValue(part, "HingeY")
    c800 = ChordAt(rootChord, tipChord, halfSpan, hy)
    zd   = DihedralLift(hy, dihedralDeg)
    xM   = sparPos * c800
    zMup = sparCam * c800 + zd + (sparDepth * c800 / rootChord) / 2.0
    zMlo = sparCam * c800 + zd - (sparDepth * c800 / rootChord) / 2.0
    xR   = rearPos * c800
    zR   = rearCam * c800 + zd

    ' 右侧 y=+800
    AddHinge part, bodyHinge, gs, "MainUpper_R", hy, xM, zMup, False
    AddHinge part, bodyHinge, gs, "MainLower_R", hy, xM, zMlo, False
    AddHinge part, bodyHinge, gs, "Rear_R",     hy, xR, zR,   False
    ' 左侧 y=-800
    AddHinge part, bodyHinge, gs, "MainUpper_L", hy, xM, zMup, True
    AddHinge part, bodyHinge, gs, "MainLower_L", hy, xM, zMlo, True
    AddHinge part, bodyHinge, gs, "Rear_L",     hy, xR, zR,   True

    part.Update

    MsgBox "中央承力框架与连接件已生成：" & vbCrLf & _
           "  CentralBox —— 中央承力盒（y=±800）" & vbCrLf & _
           "  Keel / KeelStrut —— 龙骨 + 竖支杆" & vbCrLf & _
           "  RootHinge —— 翼根折叠铰（主梁上/下 + 后梁，每侧 3 处）" & vbCrLf & _
           "下一步：运行 04_动力单元.CATScript"
End Sub

' ---------------------------------------------------------------------
' 折叠铰：铰耳(带销孔板) + 钢销。hingeY 为折叠站(正 y)，reverse=左半翼
' 铰耳位于翼外侧(y>hingeY)，销穿过铰耳并伸入中央盒区
' ---------------------------------------------------------------------
Sub AddHinge(part, body, gs, name, hingeY, xc, zc, reverse)
    Dim sgn, lugY, pinY, pinLen
    If reverse Then sgn = -1.0 Else sgn = 1.0
    lugY   = sgn * (hingeY + 6.0)      ' 耳片中心在折叠站外侧 6mm
    pinY   = sgn * (hingeY - 6.0)      ' 销起点在折叠站内侧 6mm
    pinLen = 28.0                       ' 销长 28mm，穿过耳片+盒壁

    AddLug  part, body, gs, name & "_lug", lugY, xc, zc, 60.0, 40.0, 8.0, reverse, 12.0
    AddPin  part, body, gs, name & "_pin", pinY, xc, zc, 12.0, pinLen, reverse
End Sub

' 铰耳：矩形板 + 销孔，平面在常 Y 面，沿 Y Pad thick
Sub AddLug(part, body, gs, name, yC, xc, zc, w, h, thick, reverse, holeDia)
    Dim ySketch
    If reverse Then ySketch = yC + thick / 2.0 Else ySketch = yC - thick / 2.0
    Dim planeRef
    Set planeRef = PlaneOffset(part, gs, "Y", ySketch)

    Dim sk
    Set sk = body.Sketches.Add(planeRef)
    sk.Name = name & "_sk"
    SetAxisKey sk, "Y", ySketch

    Dim f2d
    Set f2d = sk.OpenEdition()
    f2d.CreateLine xc - w / 2.0, zc - h / 2.0, xc + w / 2.0, zc - h / 2.0
    f2d.CreateLine xc + w / 2.0, zc - h / 2.0, xc + w / 2.0, zc + h / 2.0
    f2d.CreateLine xc + w / 2.0, zc + h / 2.0, xc - w / 2.0, zc + h / 2.0
    f2d.CreateLine xc - w / 2.0, zc + h / 2.0, xc - w / 2.0, zc - h / 2.0
    f2d.CreateClosedCircle xc, zc, holeDia / 2.0
    sk.CloseEdition

    part.InWorkObject = body
    Dim pad
    Set pad = part.ShapeFactory.AddNewPad(sk, thick)
    pad.Name = name
    If reverse Then pad.FirstLimit.Length = 0.0 : pad.SecondLimit.Length = thick
End Sub

' 钢销：实心圆柱，沿 Y
Sub AddPin(part, body, gs, name, yC, xc, zc, dia, len, reverse)
    Dim ySketch
    If reverse Then ySketch = yC + len / 2.0 Else ySketch = yC - len / 2.0
    Dim planeRef
    Set planeRef = PlaneOffset(part, gs, "Y", ySketch)

    Dim sk
    Set sk = body.Sketches.Add(planeRef)
    sk.Name = name & "_sk"
    SetAxisKey sk, "Y", ySketch
    Dim f2d
    Set f2d = sk.OpenEdition()
    f2d.CreateClosedCircle xc, zc, dia / 2.0
    sk.CloseEdition

    part.InWorkObject = body
    Dim pad
    Set pad = part.ShapeFactory.AddNewPad(sk, len)
    pad.Name = name
    If reverse Then pad.FirstLimit.Length = 0.0 : pad.SecondLimit.Length = len
End Sub

' ---------------------------------------------------------------------
' 通用：空心盒（对称 Pad，用于中央承力盒，在常 Y 面）
' ---------------------------------------------------------------------
Sub AddHollowBoxSym(part, body, gs, name, planeY, xc, zc, w, d, wall, halfLen)
    Dim planeRef
    Set planeRef = PlaneOffset(part, gs, "Y", planeY)
    Dim sk
    Set sk = body.Sketches.Add(planeRef)
    sk.Name = name & "_sk"
    SetAxisKey sk, "Y", planeY
    Dim f2d
    Set f2d = sk.OpenEdition()
    Dim xo1, xo2, zo1, zo2, xi1, xi2, zi1, zi2
    xo1 = xc - w / 2.0 : xo2 = xc + w / 2.0
    zo1 = zc - d / 2.0 : zo2 = zc + d / 2.0
    xi1 = xc - (w / 2.0 - wall) : xi2 = xc + (w / 2.0 - wall)
    zi1 = zc - (d / 2.0 - wall) : zi2 = zc + (d / 2.0 - wall)
    f2d.CreateLine xo1, zo1, xo2, zo1
    f2d.CreateLine xo2, zo1, xo2, zo2
    f2d.CreateLine xo2, zo2, xo1, zo2
    f2d.CreateLine xo1, zo2, xo1, zo1
    f2d.CreateLine xi1, zi1, xi2, zi1
    f2d.CreateLine xi2, zi1, xi2, zi2
    f2d.CreateLine xi2, zi2, xi1, zi2
    f2d.CreateLine xi1, zi2, xi1, zi1
    sk.CloseEdition

    part.InWorkObject = body
    Dim pad
    Set pad = part.ShapeFactory.AddNewPad(sk, halfLen)
    pad.Name = name
    pad.SecondLimit.Length = halfLen
End Sub

' ---------------------------------------------------------------------
' 通用：圆柱（实心或空心管）。key "X"/"Y"/"Z" 沿对应轴偏置 off，
' 在偏置面上画圆，沿法向 Pad。cx,cy 为该平面 H,V 草图坐标。
' ---------------------------------------------------------------------
Sub AddCylinder(part, body, gs, name, key, off, cx, cy, rOut, rIn, len1, reverse)
    Dim planeRef
    Set planeRef = PlaneOffset(part, gs, key, off)
    Dim sk
    Set sk = body.Sketches.Add(planeRef)
    sk.Name = name & "_sk"
    SetAxisKey sk, key, off
    Dim f2d
    Set f2d = sk.OpenEdition()
    f2d.CreateClosedCircle cx, cy, rOut
    If rIn > 0.0 Then f2d.CreateClosedCircle cx, cy, rIn
    sk.CloseEdition
    part.InWorkObject = body
    Dim pad
    Set pad = part.ShapeFactory.AddNewPad(sk, len1)
    pad.Name = name
    If reverse Then pad.FirstLimit.Length = 0.0 : pad.SecondLimit.Length = len1
End Sub

' ---------------------------------------------------------------------
' 工具
' ---------------------------------------------------------------------
Function ChordAt(cr, ct, hs, y)
    ChordAt = cr - (cr - ct) * (y / hs)
End Function

Function DihedralLift(y, dihedralDeg)
    DihedralLift = y * Tan(Rad(dihedralDeg))
End Function

Function Rad(deg)
    Rad = deg * 3.14159265358979 / 180.0
End Function

Function PlaneOffset(part, gs, key, off)
    Static cnt
    Dim hsf, refBase, po
    cnt = cnt + 1
    Set hsf = part.HybridShapeFactory
    If key = "X" Then
        Set refBase = part.CreateReferenceFromObject(part.OriginElements.PlaneYZ)
    ElseIf key = "Z" Then
        Set refBase = part.CreateReferenceFromObject(part.OriginElements.PlaneXY)
    Else
        Set refBase = part.CreateReferenceFromObject(part.OriginElements.PlaneZX)
    End If
    Set po = hsf.AddNewPlaneOffset(refBase, off, False)
    po.Name = "Plane_" & key & "_" & cnt
    gs.AppendHybridShape po
    Set PlaneOffset = part.CreateReferenceFromObject(po)
End Function

Sub SetAxisKey(sk, key, off)
    If key = "X" Then
        SetAxis sk, off, 0.0, 0.0, 0.0, 1.0, 0.0, 0.0, 0.0, 1.0     ' H=Y V=Z
    ElseIf key = "Z" Then
        SetAxis sk, 0.0, 0.0, off, 1.0, 0.0, 0.0, 0.0, 1.0, 0.0     ' H=X V=Y
    Else
        SetAxis sk, 0.0, off, 0.0, 1.0, 0.0, 0.0, 0.0, 0.0, 1.0     ' H=X V=Z
    End If
End Sub

Sub SetAxis(sk, ox, oy, oz, hx, hy, hz, vx, vy, vz)
    Dim a(8)
    a(0) = ox : a(1) = oy : a(2) = oz
    a(3) = hx : a(4) = hy : a(5) = hz
    a(6) = vx : a(7) = vy : a(8) = vz
    sk.SetAbsoluteAxisData a
End Sub

Function ParamValue(part, name)
    Dim p
    For Each p In part.Parameters
        If p.Name = name Then
            ParamValue = p.Value
            Exit Function
        End If
    Next
    ParamValue = 0.0
End Function

Sub EnsureParam(part, name, kind, val)
    Dim p, exists
    exists = False
    For Each p In part.Parameters
        If p.Name = name Then exists = True
    Next
    If Not exists Then
        If kind = "LENGTH" Then
            Set p = part.Parameters.CreateDimension("", "LENGTH", val)
        Else
            Set p = part.Parameters.CreateReal("", val)
        End If
        p.Rename name
    End If
End Sub

Function AddGS(part, name)
    Dim gs
    Set gs = part.HybridBodies.Add()
    gs.Name = name
    Set AddGS = gs
End Function

Function NewBody(part, name)
    Dim b
    Set b = part.Bodies.Add()
    b.Name = name
    part.InWorkObject = b
    Set NewBody = b
End Function

' =====================================================================
' 03_检查与导出.CATScript  (CATIA V5, VBScript 语法)
' 对当前活动零件：保存 CATPart + 导出 STEP（供 03_FEA 导入）。
' 质量属性检查用 GUI 更直观：零件体赋材料密度后  Measure Inertia。
' 运行前把 OUT_DIR 改成你本机 02_CATIA 目录。
' =====================================================================
Sub CATMain()
    Dim OUT_DIR
    OUT_DIR = "D:\Document\University\Personal_aircraft\02_CATIA\"

    Dim partDoc
    Set partDoc = CATIA.ActiveDocument

    ' 保存原生格式
    partDoc.SaveAs OUT_DIR & "Aircraft_Structure.CATPart"

    ' 导出 STEP（AP214/AP203）
    partDoc.ExportData OUT_DIR & "Aircraft_Structure.stp", "stp"

    MsgBox "已保存：" & vbCrLf & _
           "  " & OUT_DIR & "Aircraft_Structure.CATPart" & vbCrLf & _
           "  " & OUT_DIR & "Aircraft_Structure.stp" & vbCrLf & _
           "质量属性：菜单 工具>材料 赋密度，再 测量>惯性(Measure Inertia) 检查总质量。"
End Sub

' =====================================================================
' 06_检查与导出.CATScript  (CATIA V5, VBScript)
' 在运行完 01~05（整机建模完成）后运行：
'   1) 检查各 Body / 几何图形集是否齐全
'   2) 保存 CATPart
'   3) 导出 STEP（供 03_FEA 导入）
'
' 质量属性（材料密度 + Measure Inertia）建议手工完成，见脚本末尾提示与
' 《建模说明.md》§9。材料按 Body 赋密度：
'   CFRP 1550 / 7075-T6 铝 2810 / 芳纶 1440 / 钢 7850 kg/m^3
' =====================================================================
Sub CATMain()
    Dim OUT_DIR
    OUT_DIR = "D:\Document\University\Personal_aircraft\02_CATIA\"

    Dim partDoc, part
    Set partDoc = CATIA.ActiveDocument
    Set part = partDoc.Part

    ' ---- 1) 检查 Body ----
    Dim expected(9)
    expected(0) = "MainSpar" : expected(1) = "RearSpar" : expected(2) = "Ribs"
    expected(3) = "Skin"     : expected(4) = "CentralBox" : expected(5) = "Keel"
    expected(6) = "RootHinge": expected(7) = "Pylon"      : expected(8) = "Motor"
    expected(9) = "Propeller"

    Dim bodyList, b, i, ok
    bodyList = ""
    For i = 0 To 9
        ok = False
        For Each b In part.Bodies
            If b.Name = expected(i) Then ok = True
        Next
        If ok Then bodyList = bodyList & "  [OK] " & expected(i) & vbCrLf _
                     Else bodyList = bodyList & "  [--] " & expected(i) & vbCrLf
    Next

    ' ---- 2) 保存 + 导出 ----
    partDoc.SaveAs OUT_DIR & "Aircraft_Structure.CATPart"
    partDoc.ExportData OUT_DIR & "Aircraft_Structure.stp", "stp"

    MsgBox "整机建模检查与导出完成：" & vbCrLf & vbCrLf & _
           "Body 检查：" & vbCrLf & bodyList & vbCrLf & _
           "已导出：" & vbCrLf & _
           "  " & OUT_DIR & "Aircraft_Structure.CATPart" & vbCrLf & _
           "  " & OUT_DIR & "Aircraft_Structure.stp" & vbCrLf & vbCrLf & _
           "质量属性（手工）：" & vbCrLf & _
           "  1. 菜单 工具 > 材料 > 应用材料，按 Body 赋密度：" & vbCrLf & _
           "     翼梁/翼肋/蒙皮/中央盒/托板/桨 = CFRP 1550" & vbCrLf & _
           "     铰耳/销/龙骨/塔架 = 7075-T6 铝 2810（销用钢 7850）" & vbCrLf & _
           "     挂带 = 芳纶 1440" & vbCrLf & _
           "  2. 测量 > 惯性 (Measure Inertia) 检查整机质量（见建模说明 §9）。"
End Sub

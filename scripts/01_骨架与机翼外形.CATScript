' =====================================================================
' 01_骨架与机翼外形.CATScript  (CATIA V5, VBScript)
' 自顶向下骨架：全局参数 + 翼肋基准面 + 翼型截面(读 airfoil/*.csv) + Loft + 镜像
' 运行：工具 > 宏 > 宏... > 选择本文件 > 运行（会新建一个 Part）
' DATA_DIR 已配置为本项目的 airfoil 目录；移动项目时修改该路径。
' 注：数值字面量不带 # 后缀（CATScript 引擎不识别），全用普通数字。
' =====================================================================
Sub CATMain()
    Dim DATA_DIR
    DATA_DIR = "D:\Aircraft_Structure_design-main\02_CATIA\airfoil\"

    Dim fs
    Set fs = CreateObject("Scripting.FileSystemObject")
    If Not fs.FileExists(DATA_DIR & "fx63137_loop.csv") Or Not fs.FileExists(DATA_DIR & "e387_loop.csv") Then
        Err.Raise 516, "AirfoilData", "翼型数据文件不存在，请检查 01 宏的 DATA_DIR。"
    End If

    Dim docs, partDoc, part
    Set docs = CATIA.Documents
    Set partDoc = docs.Add("Part")
    Set part = partDoc.Part

    CreateParams part

    Dim rootChord, tipChord, halfSpan, dihedralDeg, washoutDeg, ribSpacing
    rootChord   = ParamValue(part, "RootChord")
    tipChord    = ParamValue(part, "TipChord")
    halfSpan    = ParamValue(part, "WingSpan") / 2.0
    dihedralDeg = ParamValue(part, "Dihedral")
    washoutDeg  = ParamValue(part, "Washout")
    ribSpacing  = ParamValue(part, "RibSpacing")

    Dim gsSkel
    Set gsSkel = AddGS(part, "Skeleton")

    CreateRibPlanes part, gsSkel, ribSpacing, halfSpan

    Dim dihedralLift
    dihedralLift = halfSpan * Tan(Rad(dihedralDeg))

    Dim secRoot, secTip
    Set secRoot = AddAirfoilSection(part, gsSkel, DATA_DIR & "fx63137_loop.csv", rootChord, 0.0, 0.0, 0.0, "Root_FX63137")
    Set secTip  = AddAirfoilSection(part, gsSkel, DATA_DIR & "e387_loop.csv", tipChord, halfSpan, dihedralLift, washoutDeg, "Tip_E387")
    part.Update

    Dim gsSurf
    Set gsSurf = AddGS(part, "WingSurface")

    Dim hsf, loft
    Set hsf = part.HybridShapeFactory
    Set loft = hsf.AddNewLoft()
    loft.AddSectionToLoft part.CreateReferenceFromObject(secRoot), 1, Nothing
    loft.AddSectionToLoft part.CreateReferenceFromObject(secTip), 1, Nothing
    loft.Name = "WingRightLoft"
    gsSurf.AppendHybridShape loft
    part.Update

    Dim sym
    Set sym = hsf.AddNewSymmetry(part.CreateReferenceFromObject(loft), _
                                 part.CreateReferenceFromObject(part.OriginElements.PlaneZX))
    sym.Name = "WingLeft"
    gsSurf.AppendHybridShape sym

    part.Update

    Notify "骨架与机翼外形已生成：" & vbCrLf & _
           "  - Skeleton: 参数 + 翼肋基准面 + 根/梢翼型截面" & vbCrLf & _
           "  - WingSurface: WingRightLoft (右半翼) + WingLeft (镜像)"
End Sub

' ---------------------------------------------------------------------
Function Rad(deg)
    Rad = deg * 3.14159265358979 / 180.0
End Function

Function ParamValue(part, name)
    Dim p
    For Each p In part.Parameters
        If p.Name = name Then
            ParamValue = p.Value
            Exit Function
        End If
    Next
    Err.Raise 515, "ParamValue", "缺少必要参数：" & name & "。请先运行前序宏。"
End Function

Function AddGS(part, name)
    Dim gs
    Set gs = part.HybridBodies.Add()
    gs.Name = name
    Set AddGS = gs
End Function

Sub CreateParams(part)
    Dim p, d, r
    Set p = part.Parameters
    Set d = p.CreateDimension("", "LENGTH", 13000.0) : d.Rename "WingSpan"
    Set d = p.CreateDimension("", "LENGTH", 2051.0)  : d.Rename "RootChord"
    Set d = p.CreateDimension("", "LENGTH", 1026.0)  : d.Rename "TipChord"
    Set d = p.CreateDimension("", "ANGLE", 4.0)      : d.Rename "Dihedral"
    Set d = p.CreateDimension("", "ANGLE", -2.0)     : d.Rename "Washout"
    Set d = p.CreateDimension("", "LENGTH", 450.0)   : d.Rename "RibSpacing"
    Set d = p.CreateDimension("", "LENGTH", 200.0)   : d.Rename "SparDepthRoot"
    Set d = p.CreateDimension("", "LENGTH", 40.0)    : d.Rename "SparWidth"
    Set d = p.CreateDimension("", "LENGTH", 3.0)     : d.Rename "RibThickness"
    Set d = p.CreateDimension("", "LENGTH", 2.0)     : d.Rename "SkinThickness"
    Set r = p.CreateReal("", 0.5)  : r.Rename "TaperRatio"
    Set r = p.CreateReal("", 0.30) : r.Rename "SparChordPos"
    Set r = p.CreateReal("", 0.65) : r.Rename "RearSparChordPos"
End Sub

Sub CreateRibPlanes(part, gs, spacing, halfSpan)
    Dim hsf, refZX, y, po
    Set hsf = part.HybridShapeFactory
    ' 翼肋面 = 常 Y 平面：偏移 zx plane(y=0) 沿其法向(+Y)，而非 yz(x=0) 沿 +X
    Set refZX = part.CreateReferenceFromObject(part.OriginElements.PlaneZX)
    y = spacing
    Do While y < halfSpan
        Set po = hsf.AddNewPlaneOffset(refZX, y, False)
        po.Name = "Rib_y" & CStr(CLng(y))
        gs.AppendHybridShape po
        part.UpdateObject po
        y = y + spacing
    Loop
End Sub

Function AddAirfoilSection(part, gs, csvFile, chord, ypos, zpos, thetaDeg, prefix)
    Dim hsf
    Set hsf = part.HybridShapeFactory
    Dim cosT, sinT
    cosT = Cos(Rad(thetaDeg))
    sinT = Sin(Rad(thetaDeg))

    Dim spl
    Set spl = hsf.AddNewSpline()

    Dim fso, ts, line, arr, x, y, x0, z0, x1, z1, pt, refPt, idx
    Set fso = CreateObject("Scripting.FileSystemObject")
    Set ts = fso.OpenTextFile(csvFile, 1)
    ts.ReadLine
    idx = 0
    Do While Not ts.AtEndOfStream
        line = Trim(ts.ReadLine)
        If Len(line) > 0 Then
            arr = Split(line, ",")
            x = CDbl(arr(0))
            y = CDbl(arr(1))
            x0 = x * chord
            z0 = y * chord
            x1 = x0 * cosT + z0 * sinT
            z1 = -x0 * sinT + z0 * cosT
            Set pt = hsf.AddNewPointCoord(x1, ypos, z1 + zpos)
            pt.Name = prefix & "_pt" & idx
            gs.AppendHybridShape pt
            Set refPt = part.CreateReferenceFromObject(pt)
            spl.AddPoint refPt
            idx = idx + 1
        End If
    Loop
    ts.Close
    ' 注：不调用 SetClosing——闭合截面之间的 Loft 需要 closing point，
    ' 自动化接口不便于指定，容易生成退化曲面导致 Update 失败。
    ' 保持截面开放（首尾 TE 间隙 <0.1mm），Loft 即标准开放截面扫掠，稳定。
    spl.Name = prefix & "_section"
    gs.AppendHybridShape spl
    part.UpdateObject spl
    Set AddAirfoilSection = spl
End Function

' Check sequence and refuse duplicate/partial builds before modifying the part.
Sub RequireReady(part, requiredNames, newNames)
    Dim name, b, found
    For Each name In requiredNames
        found = False
        For Each b In part.Bodies
            If b.Name = name And b.Shapes.Count > 0 Then found = True
        Next
        If Not found Then Err.Raise 513, "RequireReady", "缺少前序结构：" & name & "。请按 01 至 06 顺序运行。"
    Next
    For Each name In newNames
        For Each b In part.Bodies
            If b.Name = name Then Err.Raise 514, "RequireReady", "已存在结构或失败残留：" & name & "。请恢复运行本步骤前的模型再重试。"
        Next
    Next
End Sub

Sub Notify(message)
    MsgBox message
End Sub
